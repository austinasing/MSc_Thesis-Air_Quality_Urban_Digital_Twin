FME workspace building_method.fmw

Parameters:
- SourceDataset_GML = $(FME_MF_DIR)sofia_st2_model.gml   # Source Geography Markup Language (GML) File(s)
- DestDataset_CITYGML = $(FME_MF_DIR)sofia_elips.gml   # Destination CityGML Document

Readers:
- GML_1: GML from $(SourceDataset_GML)

Writers:
- CITYGML_1: CITYGML to $(DestDataset_CITYGML) in LL-WGS84

Building (reader GML_1)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_appearance{}.xlink_href xml_buffer, citygml_class xml_buffer, citygml_class_codeSpace xml_buffer, citygml_function{} xml_buffer, citygml_function{}.codeSpace xml_buffer, citygml_usage{} xml_buffer, citygml_usage{}.codeSpace xml_buffer, citygml_year_of_construction xml_buffer, citygml_year_of_demolition xml_buffer, citygml_roof_type xml_buffer, citygml_roof_type_codeSpace xml_buffer, citygml_measured_height xml_real64, citygml_measured_height_units xml_buffer, citygml_storeys_above_ground xml_uint64, citygml_storeys_below_ground xml_uint64, citygml_storey_heights_above_ground xml_buffer,
      citygml_storey_heights_above_ground_units xml_buffer, citygml_storey_heights_below_ground xml_buffer, citygml_storey_heights_below_ground_units xml_buffer, citygml_outer_building_installation{}.xlink_href xml_buffer, citygml_interior_building_installation{}.xlink_href xml_buffer, citygml_bounded_by{}.xlink_href xml_buffer, citygml_level_of_detail{} xml_buffer, citygml_interior_room{}.xlink_href xml_buffer, citygml_consists_of_building_part{}.xlink_href xml_buffer, citygml_address{}.xlink_href xml_buffer, _part_number xml_buffer, citygml_class_description xml_buffer, citygml_function xml_buffer, citygml_function_description xml_buffer, citygml_storeysAboveGround xml_buffer, dstrct_id xml_buffer, dstrct_obns_cyr xml_buffer, dstrct_obns_lat xml_buffer, dstrct_obns_num xml_buffer, dtm2m_median xml_buffer, fme_rejection_code xml_buffer, geom_src xml_buffer, id_kk xml_buffer, sunhrs_int_avg xml_buffer, t1600_max xml_buffer, t2100_max xml_buffer
    -> CoordinateSystemSetter
CoordinateSystemSetter
    COORDSYS = EPSG:7801
    -> CsmapReprojector
CsmapReprojector
    DEST = LL-WGS84
    GEOID_HEIGHT_GRID = $(FME_HOME)Reproject\GeoidHeightGrids\World\Egm96-Wgs84.gdc
    INTERPOLATION_TYPE = ,NearestNeighbor
    RASTER_CELL_SIZE_LOOKUP = ,PreserveCells
    RASTER_TOLERANCE = 0.0
    SOURCE = EPSG:7801
    VERTICAL_HANDLING_LOOKUP = 3D_ORTHOMETRIC_TO_ELLIPSOID
    INTERPOLATION_TYPE_NAME = Nearest Neighbor
    RASTER_CELL_SIZE = Preserve Cells
    VERTICAL_HANDLING = Orthometric height -> Geocentric or ellipsoid height
    REPROJECTED -> Building (writer CITYGML_1)
Building (writer CITYGML_1)
    attributes: citygml_target_uri xml_buffer, citygml_feature_role xml_buffer, citygml_feature_role_attr_name xml_buffer, citygml_feature_role_attr_val xml_buffer, gml_description xml_buffer, gml_name xml_buffer, citygml_creationDate xml_buffer, citygml_terminationDate xml_buffer, externalReference{}.externalObject.name xml_xml, externalReference{}.externalObject.uri xml_xml, externalReference{}.informationSystem xml_xml, citygml_generalizes_to{}.xlink_href xml_buffer, citygml_relative_to_terrain xml_char(33), citygml_relative_to_water xml_char(38), citygml_appearance{}.xlink_href xml_buffer, citygml_class xml_buffer, citygml_class_codeSpace xml_buffer, citygml_function{} xml_buffer, citygml_function{}.codeSpace xml_buffer, citygml_usage{} xml_buffer, citygml_usage{}.codeSpace xml_buffer, citygml_year_of_construction xml_buffer, citygml_year_of_demolition xml_buffer, citygml_roof_type xml_buffer, citygml_roof_type_codeSpace xml_buffer, citygml_measured_height xml_real64, citygml_measured_height_units xml_buffer, citygml_storeys_above_ground xml_uint64, citygml_storeys_below_ground xml_uint64, citygml_storey_heights_above_ground xml_buffer,
      citygml_storey_heights_above_ground_units xml_buffer, citygml_storey_heights_below_ground xml_buffer, citygml_storey_heights_below_ground_units xml_buffer, citygml_outer_building_installation{}.xlink_href xml_buffer, citygml_interior_building_installation{}.xlink_href xml_buffer, citygml_bounded_by{}.xlink_href xml_buffer, citygml_level_of_detail{} xml_buffer, citygml_interior_room{}.xlink_href xml_buffer, citygml_consists_of_building_part{}.xlink_href xml_buffer, citygml_address{}.xlink_href xml_buffer, _part_number xml_buffer, citygml_class_description xml_buffer, citygml_function xml_buffer, citygml_function_description xml_buffer, citygml_storeysAboveGround xml_buffer, dstrct_id xml_buffer, dstrct_obns_cyr xml_buffer, dstrct_obns_lat xml_buffer, dstrct_obns_num xml_buffer, dtm2m_median xml_buffer, fme_rejection_code xml_buffer, geom_src xml_buffer, id_kk xml_buffer, sunhrs_int_avg xml_buffer, t1600_max xml_buffer, t2100_max xml_buffer
CityFurniture (reader GML_1)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_appearance{}.xlink_href xml_buffer, citygml_class xml_buffer, citygml_class_codeSpace xml_buffer, citygml_function{} xml_buffer, citygml_function{}.codeSpace xml_buffer, citygml_usage{} xml_buffer, citygml_usage{}.codeSpace xml_buffer, citygml_level_of_detail{} xml_buffer, city_gml_function_description xml_buffer, citygml_class_description xml_buffer, operator xml_buffer, station_id xml_buffer
    -> CoordinateSystemSetter_2
CoordinateSystemSetter_2
    COORDSYS = EPSG:7801
    -> CsmapReprojector_2
CsmapReprojector_2
    DEST = LL-WGS84
    GEOID_HEIGHT_GRID = $(FME_HOME)Reproject\GeoidHeightGrids\World\Egm96-Wgs84.gdc
    INTERPOLATION_TYPE = ,NearestNeighbor
    RASTER_CELL_SIZE_LOOKUP = ,PreserveCells
    RASTER_TOLERANCE = 0.0
    SOURCE = EPSG:7801
    VERTICAL_HANDLING_LOOKUP = 3D_ORTHOMETRIC_TO_ELLIPSOID
    INTERPOLATION_TYPE_NAME = Nearest Neighbor
    RASTER_CELL_SIZE = Preserve Cells
    VERTICAL_HANDLING = Orthometric height -> Geocentric or ellipsoid height
    REPROJECTED -> CityFurniture (writer CITYGML_1)
CityFurniture (writer CITYGML_1)
    attributes: citygml_target_uri xml_buffer, citygml_feature_role xml_buffer, citygml_feature_role_attr_name xml_buffer, citygml_feature_role_attr_val xml_buffer, gml_description xml_buffer, gml_name xml_buffer, citygml_creationDate xml_buffer, citygml_terminationDate xml_buffer, externalReference{}.externalObject.name xml_xml, externalReference{}.externalObject.uri xml_xml, externalReference{}.informationSystem xml_xml, citygml_generalizes_to{}.xlink_href xml_buffer, citygml_relative_to_terrain xml_char(33), citygml_relative_to_water xml_char(38), citygml_appearance{}.xlink_href xml_buffer, citygml_class xml_buffer, citygml_class_codeSpace xml_buffer, citygml_function{} xml_buffer, citygml_function{}.codeSpace xml_buffer, citygml_usage{} xml_buffer, citygml_usage{}.codeSpace xml_buffer, citygml_level_of_detail{} xml_buffer, city_gml_function_description xml_buffer, citygml_class_description xml_buffer, operator xml_buffer, station_id xml_buffer
CityModel (reader GML_1)
    attributes: citygml_target_uri xml_buffer, gml_description xml_buffer, gml_name xml_buffer, citygml_city_object_member{}.xlink_href xml_buffer, citygml_appearance_member{}.xlink_href xml_buffer, gml_feature_member{}.xlink_href xml_buffer
    -> CityModel (writer CITYGML_1)
CityModel (writer CITYGML_1)
    attributes: citygml_target_uri xml_buffer, gml_description xml_buffer, gml_name xml_buffer, citygml_city_object_member{}.xlink_href xml_buffer, citygml_appearance_member{}.xlink_href xml_buffer, gml_feature_member{}.xlink_href xml_buffer
